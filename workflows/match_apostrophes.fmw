FME workspace match_apostrophes.fmw

Parameters:
- SourceDataset_CSV2 = C:\Users\lucyr\Documents\Databases\FinalProject697\ebd_US-MA_relSep-2020\ebd_US-MA_relSep-2020.txt   # Source CSV (Comma Separated Value) File(s)
- SourceDataset_CSV2_3 = C:\Users\lucyr\Documents\Databases\FinalProject697\extra\MARC_eBird_accept_species.csv   # Source CSV (Comma Separated Value) File(s)
- DestDataset_CSV2 = C:\Users\lucyr\Documents\Databases\FinalProject697\eBird_filtered   # Destination CSV (Comma Separated Value) Folder

Readers:
- CSV2_1: CSV2 from $(SourceDataset_CSV2)
- CSV2_2: CSV2 from $(SourceDataset_CSV2_3)

Writers:
- CSV2_3: CSV2 to $(DestDataset_CSV2)

Note: CSV: ebd_US-MA_relSep-2020 [CSV2]
CSV (reader CSV2_1)
    attributes: GLOBAL UNIQUE IDENTIFIER string, LAST EDITED DATE string, TAXONOMIC ORDER uint16, CATEGORY string, COMMON NAME string, SCIENTIFIC NAME string, SUBSPECIES COMMON NAME string, SUBSPECIES SCIENTIFIC NAME string, OBSERVATION COUNT string, BREEDING BIRD ATLAS CODE string, BREEDING BIRD ATLAS CATEGORY string, AGE/SEX string, COUNTRY string, COUNTRY CODE string, STATE string, STATE CODE string, COUNTY string, COUNTY CODE string, IBA CODE string, BCR CODE uint8, USFWS CODE string, ATLAS BLOCK string, LOCALITY string, LOCALITY ID string, LOCALITY TYPE string, LATITUDE y_coordinate, LONGITUDE x_coordinate, OBSERVATION DATE string, TIME OBSERVATIONS STARTED string, OBSERVER ID string,
      SAMPLING EVENT IDENTIFIER string, PROTOCOL TYPE string, PROTOCOL CODE string, PROJECT CODE string, DURATION MINUTES uint16, EFFORT DISTANCE KM real32, EFFORT AREA HA real64, NUMBER OBSERVERS uint8, ALL SPECIES REPORTED uint8, GROUP IDENTIFIER string, HAS MEDIA uint8, APPROVED uint8, REVIEWED uint8, REASON string, TRIP COMMENTS string, SPECIES COMMENTS string, col46 string
    -> StringPairReplacer
StringPairReplacer
    CASE = no
    MAP = ' ' ’ '
    SRC_ATTRS = COMMON NAME
    -> FeatureMerger [REQUESTOR]
Note: CSV: MARC_eBird_accept_species [CSV2]
CSV (reader CSV2_2)
    attributes: common name string
    -> StringPairReplacer_2
StringPairReplacer_2
    CASE = no
    MAP = ’ '
    SRC_ATTRS = common name
    -> FeatureMerger [SUPPLIER]
FeatureMerger
    ATTR_ACCUM_MODE = Merge Supplier
    ATTR_CONFLICT_RES = Use Requestor
    IGNORE_NULLS = No
    JOIN_KEYS = @Value(COMMON NAME) @Value(common name) AUTO
    MERGE_TYPE = Attributes Only
    PROCESS_DUPS = NO
    REJECT_NULL_MISSING_KEYS = No
    SUPPLIERS_FIRST = No
    MERGED -> FeatureMerger_Merged
    MERGED -> match_ebird_with_apostrophes (writer CSV2_3)
    USED_SUPPLIER -> FeatureMerger_UsedSupplier
    UNUSED_SUPPLIER -> FeatureMerger_UnusedSupplier
    <REJECTED> -> FeatureMerger__Rejected_
FeatureMerger_Merged: Inspector
match_ebird_with_apostrophes (writer CSV2_3)
    attributes: GLOBAL UNIQUE IDENTIFIER string, LAST EDITED DATE string, TAXONOMIC ORDER uint16, CATEGORY string, COMMON NAME string, SCIENTIFIC NAME string, SUBSPECIES COMMON NAME string, SUBSPECIES SCIENTIFIC NAME string, OBSERVATION COUNT string, BREEDING BIRD ATLAS CODE string, BREEDING BIRD ATLAS CATEGORY string, AGE/SEX string, COUNTRY string, COUNTRY CODE string, STATE string, STATE CODE string, COUNTY string, COUNTY CODE string, IBA CODE string, BCR CODE uint8, USFWS CODE string, ATLAS BLOCK string, LOCALITY string, LOCALITY ID string, LOCALITY TYPE string, LATITUDE y_coordinate, LONGITUDE x_coordinate, OBSERVATION DATE string, TIME OBSERVATIONS STARTED string, OBSERVER ID string,
      SAMPLING EVENT IDENTIFIER string, PROTOCOL TYPE string, PROTOCOL CODE string, PROJECT CODE string, DURATION MINUTES uint16, EFFORT DISTANCE KM real32, EFFORT AREA HA real64, NUMBER OBSERVERS uint8, ALL SPECIES REPORTED uint8, GROUP IDENTIFIER string, HAS MEDIA uint8, APPROVED uint8, REVIEWED uint8, REASON string, TRIP COMMENTS string, SPECIES COMMENTS string, col46 string
FeatureMerger_UsedSupplier: Inspector
FeatureMerger_UnusedSupplier: Inspector
FeatureMerger__Rejected_: Inspector
