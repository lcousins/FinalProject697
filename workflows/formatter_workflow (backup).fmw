FME workspace formatter_workflow (backup).fmw

Parameters:
- SourceDataset_CSV2 = $(FME_MF_DIR)extra\geocoded_marc_csv.csv   # Source CSV (Comma Separated Value) File(s)
- DestDataset_CSV2 = $(FME_MF_DIR)Liam's writers   # Destination CSV (Comma Separated Value) Folder
- DestDataset_CSV2_2 = $(FME_MF_DIR)eBird_filtered   # Destination CSV (Comma Separated Value) Folder
- DestDataset_POSTGIS = 697dd   # Connection
- SourceDataset_CSV2_5 = C:\Users\lucyr\Documents\Databases\FinalProject697\eBird_filtered\ebird_filtered_with_apostrophes.csv   # Source CSV (Comma Separated Value) File(s)
- DestDataset_POSTGIS_4 = 697dd   # Connection

Readers:
- CSV2_1: CSV2 from $(SourceDataset_CSV2)
- CSV2_3: CSV2 from $(SourceDataset_CSV2_5)

Writers:
- CSV2_4: CSV2 to $(DestDataset_CSV2)
- CSV2_5: CSV2 to $(DestDataset_CSV2_2)
- POSTGIS_1: POSTGIS to $(DestDataset_POSTGIS)
- POSTGIS_3: POSTGIS to $(DestDataset_POSTGIS_4)

NullAttributeMapper
    ATTRCHOICE = Selected Attributes
    ATTRLIST = county latitude longitude observers species
    NULL_TREATMENT = Missing
    SOURCE_ATTR_VAL = Null
    -> TestFilter
Note: these do seem to all have numeric values but it probably doesn't matter since none have a usable date range
TestFilter
    DEFAULT_VALUE = <UNFILTERED>
    TEST_LIST = "BOOL_OP,AND,COMPOSITE_TEST,""""""1"""""",TEST_CLAUSE,TEST @Value(count) TYPE NUM",@Value(count) TYPE NUM
    @Value(count) TYPE NUM -> DateTimeConverter
    <UNFILTERED> -> TestFilter__Unfiltered_
Note: rejects records that don't have both an arrival and departure date. (most of these don't have a date at all, some have one date)
DateTimeConverter
    DATETIME_ATTR = arrival_da departure_
    IN_FORMAT = %m/%d/%Y$
    OUT_FORMAT = %Y-%m-%d
    PASSTHROUGH = NO
    REPAIR_INPUT = YES
    -> MARC_Formatted (writer CSV2_4)
    <REJECTED> -> DateTimeConverter__Rejected_
DateTimeConverter__Rejected_: Inspector
TestFilter__Unfiltered_: Inspector
Note: ebird_filtered_with_apostrophes
CSV (reader CSV2_3)
    attributes: GLOBAL UNIQUE IDENTIFIER string, LAST EDITED DATE string, TAXONOMIC ORDER uint16, CATEGORY string, COMMON NAME string, SCIENTIFIC NAME string, SUBSPECIES COMMON NAME string, SUBSPECIES SCIENTIFIC NAME string, OBSERVATION COUNT string, BREEDING BIRD ATLAS CODE string, BREEDING BIRD ATLAS CATEGORY string, AGE/SEX string, COUNTRY string, COUNTRY CODE string, STATE string, STATE CODE string, COUNTY string, COUNTY CODE string, IBA CODE string, BCR CODE uint8, USFWS CODE string, ATLAS BLOCK string, LOCALITY string, LOCALITY ID string, LOCALITY TYPE string, LATITUDE y_coordinate, LONGITUDE x_coordinate, OBSERVATION DATE string, TIME OBSERVATIONS STARTED string, OBSERVER ID string,
      SAMPLING EVENT IDENTIFIER string, PROTOCOL TYPE string, PROTOCOL CODE string, PROJECT CODE string, DURATION MINUTES uint16, EFFORT DISTANCE KM real32, EFFORT AREA HA real64, NUMBER OBSERVERS uint8, ALL SPECIES REPORTED uint8, GROUP IDENTIFIER string, HAS MEDIA uint8, APPROVED uint8, REVIEWED uint8, REASON string, TRIP COMMENTS string, SPECIES COMMENTS string, col46 string, common name string
    -> DateTimeConverter_2
DateTimeConverter_2
    DATETIME_ATTR = OBSERVATION DATE
    OUT_FORMAT = %Y-%m-%d
    PASSTHROUGH = NO
    REPAIR_INPUT = YES
    -> NullAttributeMapper_2
NullAttributeMapper_2
    ATTRCHOICE = Selected Attributes
    ATTRLIST = COMMON NAME COUNTY LATITUDE LONGITUDE OBSERVATION DATE
    NULL_TREATMENT = Missing
    SOURCE_ATTR_VAL = Null
    -> ebird_formatted (writer CSV2_5)
    -> NullAttributeMapper_2_Output
    -> ebird_2 (writer POSTGIS_3)
NullAttributeMapper_2_Output: Inspector
ebird_formatted (writer CSV2_5)
    attributes: COMMON NAME string, SCIENTIFIC NAME string, OBSERVATION COUNT string, STATE string, COUNTY string, LOCALITY string, LATITUDE y_coordinate, LONGITUDE x_coordinate, OBSERVATION DATE string, OBSERVER ID string
ebird_2 (writer POSTGIS_3)
    attributes: global_unique_identifier text, last_edited_date text, taxonomic_order int4, category text, common_name text, scientific_name text, subspecies_common_name text, subspecies_scientific_name text, observation_count text, breeding_bird_atlas_code text, breeding_bird_atlas_category text, age_sex text, country text, country_code text, state text, state_code text, county text, county_code text, iba_code text, bcr_code int2, usfws_code text, atlas_block text, locality text, locality_id text, locality_type text, latitude float8, longitude float8, observation_date text, time_observations_started text, observer_id text,
      sampling_event_identifier text, protocol_type text, protocol_code text, project_code text, duration_minutes int4, effort_distance_km float4, effort_area_ha float8, number_observers int2, all_species_reported int2, group_identifier text, has_media int2, approved int2, reviewed int2, reason text, trip_comments text, species_comments text, col46 text, common_name00 text

Bookmark: MARC_badly_formatted
CSV (reader CSV2_1) [off]
    attributes: agol_City string, agol_Subre string, agol_Match string, agol_Score real32, species string, count string, location string, county string, arrival_da string, departure_ string, observers string, longitude x_coordinate, latitude y_coordinate
    -> NullAttributeMapper

Bookmark: marc_dates_formatted
MARC_Formatted (writer CSV2_4)
    attributes: agol_City string, agol_Subre string, agol_Match string, agol_Score real32, species string, count string, location string, county string, arrival_da string, departure_ string, observers string, longitude x_coordinate, latitude y_coordinate
