FME workspace matcher_test.fmw

Parameters:
- SourceDataset_CSV2_5 = C:\Users\Asus\Documents\GitHub\FinalProject697\.csv\MARC_eBird_accept_species.txt   # Source CSV (Comma Separated Value) File(s)
- SourceDataset_CSV2 = C:\Users\Asus\Documents\GitHub\FinalProject697\.csv\ebird_marc_accept_full.csv   # Source CSV (Comma Separated Value) File(s)
- SourceDataset_CSV2_4 = C:\Users\Asus\Documents\GitHub\FinalProject697\.csv\geocoded_marc_csv.csv   # Source CSV (Comma Separated Value) File(s)

Readers:
- CSV2_1: CSV2 from $(SourceDataset_CSV2_5)
- CSV2_2: CSV2 from $(SourceDataset_CSV2)
- CSV2_3: CSV2 from $(SourceDataset_CSV2_4)

CSV (reader CSV2_2) [off]
    attributes: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
geocoded_marc_csv (reader CSV2_3)
    attributes: agol_City string, agol_Subre string, agol_Match string, agol_Score real32, species string, count string, location string, county string, arrival_da string, departure_ string, observers string, longitude x_coordinate, latitude y_coordinate
    -> StringReplacer
StringReplacer
    CASE = NO
    FIND_TEXT = \'
    NO_MATCH = _FME_NO_OP_
    REGEXP = YES
    REPLACE_TEXT = _
    SRC_ATTRS = species
    -> FeatureMerger [REQUESTOR]
CSV (reader CSV2_1)
    attributes: common_name string
    -> StringReplacer_2
StringReplacer_2
    CASE = NO
    FIND_TEXT = \'
    NO_MATCH = _FME_NO_OP_
    REGEXP = YES
    REPLACE_TEXT = _
    SRC_ATTRS = common_name
    -> FeatureMerger [SUPPLIER]
FeatureMerger
    ATTR_ACCUM_MODE = Merge Supplier
    ATTR_CONFLICT_RES = Use Requestor
    IGNORE_NULLS = No
    JOIN_KEYS = @Value(species) @Value(common_name) AUTO
    MERGE_TYPE = Attributes Only
    PROCESS_DUPS = NO
    REJECT_NULL_MISSING_KEYS = No
    SUPPLIERS_FIRST = No
