FME workspace delete_this(redundant_with_geocode_marc).fmw

Parameters:
- SourceDataset_CSV2_2 = $(FME_MF_DIR)marc website public database 2020_10_27.csv   # Source CSV (Comma Separated Value) File(s)
- DestDataset_FILEGDB = geocoded_marc   # File Geodatabase

Readers:
- CSV2_3: CSV2 from $(SourceDataset_CSV2_2)

Writers:
- FILEGDB_1: FILEGDB to $(DestDataset_FILEGDB)

ArcGISOnlineConnector
    OPERATION_TYPE = List
    PARAMETER_SETUP = _FME_CONTENT_SOURCE_TYPE]User]_FME_GROUP_ID]<Unused>]_FME_FOLDER_ID]162157dff8ff4a14a0ab6cf9ba13125d]_FME_INCLUDE_SUBFOLDERS]No]_LIST_FME_ATTRIBUTES_TO_ADD]"_id _name _file_or_folder _full_path _private_url"]FME_CONTROLLER_QUERY_FILE]esri_agol_deps/List.fme
    __arcgisonlineconnector_connection = lcousins_UMass_Amherst
    -> ArcGISOnlineBatchGeocoder
    Initiator -> ArcGISOnlineBatchGeocoder
ArcGISOnlineBatchGeocoder
    AGOL_TOKEN =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
    AUTH_TYPE = Token
    Address = @Value(location)
    CountryCode = Massachusetts
    GEOCODING_TYPE = Components
    MAXBATCHSIZE = 150
    Region = @Value(county)
    SERVER_NAME = https://geocode.arcgis.com
    Geocoded -> CSV (writer FILEGDB_1)

Bookmark: Reader Feature Types
CSV (reader CSV2_3)
    attributes: pkid uint16, marc_number string, accept string, species string, count string, location string, county string, arrival_date string, departure_date string, observers string, report uint8, report_link string, col12 string, col13 string, col14 string, col15 string, col16 string, col17 string, col18 string, col19 string, col20 string, col21 string, col22 string, col23 string, col24 string, col25 string
    -> ArcGISOnlineConnector

Bookmark: Writer Feature Types
CSV (writer FILEGDB_1)
    attributes: location text(2048), county text(2048), species text(2048), arrival_date text(2048), departure_date text(2048)
