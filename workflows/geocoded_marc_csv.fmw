FME workspace geocoded_marc_csv.fmw

Parameters:
- SourceDataset_SHAPEFILE = $(FME_MF_DIR)Geocoded MARC shapefile\ArcGISOnlineBatchGeocoder_Geocoded_point.shp   # Source Esri Shapefile(s)
- DestDataset_CSV2 = C:\Users\lucyr\Documents\Databases\FinalProject697   # Destination CSV (Comma Separated Value) Folder

Readers:
- SHAPEFILE_1: SHAPEFILE from $(SourceDataset_SHAPEFILE)

Writers:
- CSV2_1: CSV2 to $(DestDataset_CSV2)

ArcGISOnlineBatchGeocoder_Geocoded_point (reader SHAPEFILE_1)
    attributes: agol_City char(200), agol_Count char(200), agol_Match char(200), agol_Posta char(200), agol_Pos00 char(200), agol_Regio char(200), agol_Score char(200), agol_Side char(200), agol_Statu char(200), agol_Subre char(200), agol_StDir char(200), agol_StNam char(200), agol_StPre char(200), agol_StP00 char(200), agol_StTyp char(200), agol_AddNu char(200), agol_Add00 char(200), agol_Resul char(200), agol_Neigh char(200), agol_Addre char(200), agol_Dista char(200), agol_Addr_ char(200), species char(254), count char(254), location char(254), county char(254), arrival_da char(254), departure_ char(254), observers char(254), _id char(200),
      _name char(200), _file_or_f char(200), _full_path char(200), _private_u char(200)
    -> CoordinateExtractor
CoordinateExtractor
    LIST_NAME = _indices
    MODE = All Coordinates
    -> AttributeRenamer
AttributeRenamer
    ATTR_TABLE:
      RENAME_SET_DEFAULT _indices{0}.x > _indices__.x
      RENAME_SET_DEFAULT _indices{0}.y > _indices__.y
      RENAME_SET_DEFAULT _indices{0}.z > _indices__.z
    -> geocoded_marc_csv (writer CSV2_1)
geocoded_marc_csv (writer CSV2_1)
    attributes: agol_City string, agol_Count string, agol_Match string, agol_Regio string, agol_Score string, agol_Statu string, agol_Subre string, agol_StNam string, agol_Resul string, species string, count string, location string, county string, arrival_da string, departure_ string, observers string, _indices__.x string, _indices__.y string, _indices__.z string
