FME workspace ebird_full.fmw

Parameters:
- SourceDataset_CSV2 = C:\Users\Asus\Documents\GitHub\FinalProject697\ebd_US-MA_relSep-2020.txt   # Source CSV (Comma Separated Value) File(s)
- SourceDataset_CSV2_3 = C:\Users\Asus\Documents\GitHub\FinalProject697\.csv\MARC_eBird_accept_species.txt   # Source CSV (Comma Separated Value) File(s)
- DestDataset_POSTGIS = ECO697   # Connection
- DestDataset_CSV2 = C:\Users\Asus\Documents\GitHub\FinalProject697\Liam's writers   # Destination CSV (Comma Separated Value) Folder

Readers:
- CSV2_1: CSV2 from $(SourceDataset_CSV2) in EPSG:4326
- CSV2_2: CSV2 from $(SourceDataset_CSV2_3)

Writers:
- POSTGIS_1: POSTGIS to $(DestDataset_POSTGIS) in EPSG:4326
- CSV2_3: CSV2 to $(DestDataset_CSV2)

Note: full ebird data with just the needed attributes
CSV (reader CSV2_1)
    attributes: COMMON NAME string, SCIENTIFIC NAME string, OBSERVATION COUNT string, COUNTY string, LOCALITY string, LATITUDE y_coordinate, LONGITUDE x_coordinate, OBSERVATION DATE string, SAMPLING EVENT IDENTIFIER string, SPECIES COMMENTS string
    -> StringReplacer
Note: change ' to _
StringReplacer
    CASE = NO
    FIND_TEXT = \’
    NO_MATCH = _FME_NO_OP_
    REGEXP = YES
    REPLACE_TEXT = _
    SRC_ATTRS = COMMON NAME
    -> FeatureMerger [REQUESTOR]
Note: MARC_eBird_accept_species
CSV (reader CSV2_2)
    attributes: common_name string
    -> FeatureMerger [SUPPLIER]
FeatureMerger
    ATTR_ACCUM_MODE = Merge Supplier
    ATTR_CONFLICT_RES = Use Requestor
    IGNORE_NULLS = No
    JOIN_KEYS = @Value(COMMON NAME) @Value(common_name) AUTO
    MERGE_TYPE = Attributes Only
    PROCESS_DUPS = NO
    REJECT_NULL_MISSING_KEYS = No
    SUPPLIERS_FIRST = No
    MERGED -> target_ebird (writer CSV2_3)
target_ebird (writer CSV2_3)
    attributes: COMMON NAME string, SCIENTIFIC NAME string, OBSERVATION COUNT string, COUNTY string, LOCALITY string, LATITUDE y_coordinate, LONGITUDE x_coordinate, OBSERVATION DATE string, SAMPLING EVENT IDENTIFIER string, SPECIES COMMENTS string
Note: ebird_filtered: ECO697 [POSTGIS]
Note: ebird_filtered: ECO697 [POSTGIS]
ebird_filtered (writer POSTGIS_1) [off]
    attributes: common_name text
