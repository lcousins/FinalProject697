FME workspace test_fme.fmw

Parameters:
- SourceDataset_CSV2 = $(FME_MF_DIR)ebd_US-MA_relSep-2020\ebd_US-MA_relSep-2020.txt   # Source CSV (Comma Separated Value) File(s)
- DestDataset_CSV2 = C:\Users\lucyr\Documents\Databases\FinalProject697   # Destination CSV (Comma Separated Value) Folder
- SourceDataset_CSV2_2 = $(FME_MF_DIR)mock_marc.csv   # Source CSV (Comma Separated Value) File(s)
- DestDataset_CSV2_3 = unfiltered_dates   # Destination CSV (Comma Separated Value) Folder

Readers:
- CSV2_1: CSV2 from $(SourceDataset_CSV2)
- CSV2_3: CSV2 from $(SourceDataset_CSV2_2)

Writers:
- CSV2_2: CSV2 to $(DestDataset_CSV2)
- CSV2_4: CSV2 to $(DestDataset_CSV2_3)

DateTimeConverter
    DATETIME_ATTR = Arrival date Departure date
    IN_FORMAT = %d/%m/%Y$
    OUT_FORMAT = FME
    PASSTHROUGH = NO
    REPAIR_INPUT = YES
    -> DatesFilter_2
    <REJECTED> -> BadFormatDates (writer CSV2_4)
DatesFilter_2: TestFilter
    DEFAULT_VALUE = <UNFILTERED>
    TEST_LIST:
      "BOOL_OP,AND,COMPOSITE_TEST,""""""1 AND 2"""""",TEST_CLAUSE,CASE_INSENSITIVE_TEST @Value(Arrival date) TYPE DATE
      TEST @Value(Departure date) TYPE DATE",@Value(OBSERVATION DATE) TYPE DATE
    @Value(OBSERVATION DATE) TYPE DATE -> TestFilter
Note: this csv contains dates with two digit ending (1/1/20) and date entries that have extra words
BadFormatDates (writer CSV2_4)
    attributes: MARC number string, Species string, # uint8, Location string, County string, Arrival date string, Departure date string, Observer string
DateTimeConverter_2
    DATETIME_ATTR = OBSERVATION DATE
    IN_FORMAT = %Y-%m-%d$
    OUT_FORMAT = FME
    PASSTHROUGH = NO
    REPAIR_INPUT = YES
    -> DatesFilter
DatesFilter: TestFilter
    DEFAULT_VALUE = <UNFILTERED>
    TEST_LIST = "BOOL_OP,OR,COMPOSITE_TEST,""""""1"""""",TEST_CLAUSE,TEST @Value(OBSERVATION DATE) TYPE DATE",@Value(OBSERVATION DATE) TYPE DATE
    @Value(OBSERVATION DATE) TYPE DATE -> TestFilter
Note: this filter checks if the ebird observation date is in the marc date range. It is not really working right now, but that is probably because we are only working with 100,000 records. Also, we will need to add species/location matching eventually.
TestFilter
    DEFAULT_VALUE = <UNFILTERED>
    TEST_LIST = "BOOL_OP,AND,COMPOSITE_TEST,""""""1"""""",TEST_CLAUSE,TEST @Value(OBSERVATION DATE) RANGE [@Evaluate(@Value(Arrival date)),@Evaluate(@Value(Departure date))]",@Value(OBSERVATION DATE) RANGE [@Evaluate(@Value(Arrival date)),@Evaluate(@Value(Departure date))]
    @Value(OBSERVATION DATE) RANGE [@Evaluate(@Value(Arrival date)),@Evaluate(@Value(Departure date))] -> ebird_csv (writer CSV2_2)
    <UNFILTERED> -> ebird_csv (writer CSV2_2)

Bookmark: mock_marc dataset
CSV (reader CSV2_3)
    attributes: MARC number string, Species string, # uint8, Location string, County string, Arrival date string, Departure date string, Observer string
    -> DateTimeConverter

Bookmark: ebird (max records = 100,000)
CSV (reader CSV2_1)
    attributes: GLOBAL UNIQUE IDENTIFIER string, LAST EDITED DATE string, TAXONOMIC ORDER uint16, CATEGORY string, COMMON NAME string, SCIENTIFIC NAME string, SUBSPECIES COMMON NAME string, SUBSPECIES SCIENTIFIC NAME string, OBSERVATION COUNT string, BREEDING BIRD ATLAS CODE string, BREEDING BIRD ATLAS CATEGORY string, AGE/SEX string, COUNTRY string, COUNTRY CODE string, STATE string, STATE CODE string, COUNTY string, COUNTY CODE string, IBA CODE string, BCR CODE uint8, USFWS CODE string, ATLAS BLOCK string, LOCALITY string, LOCALITY ID string, LOCALITY TYPE string, LATITUDE y_coordinate, LONGITUDE x_coordinate, OBSERVATION DATE string, TIME OBSERVATIONS STARTED string, OBSERVER ID string,
      SAMPLING EVENT IDENTIFIER string, PROTOCOL TYPE string, PROTOCOL CODE string, PROJECT CODE string, DURATION MINUTES uint16, EFFORT DISTANCE KM real32, EFFORT AREA HA real64, NUMBER OBSERVERS uint8, ALL SPECIES REPORTED uint8, GROUP IDENTIFIER string, HAS MEDIA uint8, APPROVED uint8, REVIEWED uint8, REASON string, TRIP COMMENTS string, SPECIES COMMENTS string, col46 string
    -> DateTimeConverter_2

Bookmark: Writer Feature Types
ebird_csv (writer CSV2_2)
    attributes: MARC number string, Species string, # uint8, Location string, County string, Arrival date string, Departure date string, Observer string, COMMON NAME string, SCIENTIFIC NAME string, STATE string, LATITUDE y_coordinate, LONGITUDE x_coordinate, OBSERVATION DATE string
