FME workspace formatter_workflow.fmw

Parameters:
- SourceDataset_CSV2 = $(FME_MF_DIR)geocoded_marc_csv.csv   # Source CSV (Comma Separated Value) File(s)
- DestDataset_CSV2 = C:\Users\lucyr\Documents\Databases\FinalProject697   # Destination CSV (Comma Separated Value) Folder
- SourceDataset_CSV2_3 = $(FME_MF_DIR)eBird_filtered\ebird_marc_accept_full.csv   # Source CSV (Comma Separated Value) File(s)
- DestDataset_CSV2_2 = C:\Users\lucyr\Documents\Databases\FinalProject697   # Destination CSV (Comma Separated Value) Folder

Readers:
- CSV2_1: CSV2 from $(SourceDataset_CSV2)
- CSV2_2: CSV2 from $(SourceDataset_CSV2_3)

Writers:
- CSV2_3: CSV2 to $(DestDataset_CSV2)
- CSV2_4: CSV2 to $(DestDataset_CSV2_2)

NullAttributeMapper
    ATTRCHOICE = Selected Attributes
    ATTRLIST = county latitude longitude observers species
    NULL_TREATMENT = Missing
    SOURCE_ATTR_VAL = Null
    -> TestFilter
TestFilter
    DEFAULT_VALUE = <UNFILTERED>
    TEST_LIST = "BOOL_OP,AND,COMPOSITE_TEST,""""""1"""""",TEST_CLAUSE,TEST @Value(count) TYPE NUM",@Value(count) TYPE NUM
    @Value(count) TYPE NUM -> DateTimeConverter
    <UNFILTERED> -> TestFilter__Unfiltered_
DateTimeConverter
    DATETIME_ATTR = arrival_da departure_
    IN_FORMAT = %m/%d/%Y$
    OUT_FORMAT = %Y-%m-%d
    PASSTHROUGH = NO
    REPAIR_INPUT = YES
    -> MARC_Formatted (writer CSV2_3)
    <REJECTED> -> DateTimeConverter__Rejected_
DateTimeConverter__Rejected_: Inspector
TestFilter__Unfiltered_: Inspector
CSV (reader CSV2_2)
    attributes: Species string, TAXONOMIC ORDER uint16, CATEGORY string, COMMON NAME string, SCIENTIFIC NAME string, OBSERVATION COUNT string, COUNTRY string, COUNTRY CODE string, STATE string, STATE CODE string, COUNTY string, COUNTY CODE string, LOCALITY string, LOCALITY ID string, LOCALITY TYPE string, LATITUDE y_coordinate, LONGITUDE x_coordinate, OBSERVATION DATE string, OBSERVER ID string, NUMBER OBSERVERS uint8, ALL SPECIES REPORTED uint8, TRIP COMMENTS string, SPECIES COMMENTS string
    -> TestFilter_2
TestFilter_2
    DEFAULT_VALUE = <UNFILTERED>
    TEST_LIST = "BOOL_OP,OR,COMPOSITE_TEST,""""""1"""""",TEST_CLAUSE,TEST @Value(OBSERVATION COUNT) TYPE INT",@Value(OBSERVATION COUNT) TYPE INT
    @Value(OBSERVATION COUNT) TYPE INT -> DateTimeConverter_2
DateTimeConverter_2
    DATETIME_ATTR = OBSERVATION DATE
    OUT_FORMAT = %Y-%m-%d
    PASSTHROUGH = NO
    REPAIR_INPUT = YES
    -> NullAttributeMapper_2
NullAttributeMapper_2
    ATTRCHOICE = Selected Attributes
    ATTRLIST = COMMON NAME COUNTY LATITUDE LONGITUDE OBSERVATION DATE
    NULL_TREATMENT = Missing
    SOURCE_ATTR_VAL = Null
    -> ebird_formatted (writer CSV2_4)
ebird_formatted (writer CSV2_4)
    attributes: COMMON NAME string, SCIENTIFIC NAME string, OBSERVATION COUNT string, STATE string, COUNTY string, LOCALITY string, LATITUDE y_coordinate, LONGITUDE x_coordinate, OBSERVATION DATE string, OBSERVER ID string

Bookmark: MARC_badly_formatted
CSV (reader CSV2_1)
    attributes: agol_City string, agol_Subre string, agol_Match string, agol_Score real32, species string, count string, location string, county string, arrival_da string, departure_ string, observers string, longitude x_coordinate, latitude y_coordinate
    -> NullAttributeMapper

Bookmark: marc_dates_formatted
MARC_Formatted (writer CSV2_3)
    attributes: agol_City string, agol_Subre string, agol_Match string, agol_Score real32, species string, count string, location string, county string, arrival_da string, departure_ string, observers string, longitude x_coordinate, latitude y_coordinate
