FME workspace filter_ebird_marc_accept.fmw

Parameters:
- SourceDataset_CSV2 = $(FME_MF_DIR)ebd_US-MA_relSep-2020\ebd_US-MA_relSep-2020.txt   # Source CSV (Comma Separated Value) File(s)
- DestDataset_CSV2 = ebd_marc_acceptsList   # Destination CSV (Comma Separated Value) Folder
- SourceDataset_XLSXR = $(FME_MF_DIR)MARC_eBird_accept_species.xlsx   # Source Microsoft Excel File(s)

Readers:
- CSV2_1: CSV2 from $(SourceDataset_CSV2)
- XLSXR_1: XLSXR from $(SourceDataset_XLSXR)

Writers:
- CSV2_2: CSV2 to $(DestDataset_CSV2)

FormatTester_name: TestFilter
    DEFAULT_VALUE = <UNFILTERED>
    TEST_LIST = "BOOL_OP,OR,COMPOSITE_TEST,""""""1"""""",TEST_CLAUSE,TEST @Value(CATEGORY) = species",@Value(CATEGORY) = species
    @Value(CATEGORY) = species -> FeatureJoiner [RIGHT]
Sheet1 (reader XLSXR_1)
    attributes: Species char(34)
    -> StringReplacer
Note: BEFORE YOU RUN: make sure max features to read is set / (in navigator panel, ebird reader > Parameters > Features to Read > Max Features to Read (~100000 is a good number)
StringReplacer
    CASE = YES
    FIND_TEXT = " (eB)"
    NO_MATCH = _FME_NO_OP_
    REGEXP = NO
    SRC_ATTRS = Species
    -> FeatureJoiner [LEFT]
FeatureJoiner
    ATTR_CONFLICT_RES = Use Left
    GEOMETRY_HANDLING = Use Left
    JOIN_KEYS = Species COMMON NAME AUTO
    JOIN_MODE = Inner
    JOINED -> ebird_filtered (writer CSV2_2)
    JOINED -> SpeciesInMarc
    UNJOINED_RIGHT -> SpeciesNotInMARC
    <REJECTED> -> SpeciesNotInMARC
SpeciesInMarc: Inspector
SpeciesNotInMARC: Inspector

Bookmark: Input eBird CSV
CSV (reader CSV2_1)
    attributes: GLOBAL UNIQUE IDENTIFIER string, LAST EDITED DATE string, TAXONOMIC ORDER uint16, CATEGORY string, COMMON NAME string, SCIENTIFIC NAME string, SUBSPECIES COMMON NAME string, SUBSPECIES SCIENTIFIC NAME string, OBSERVATION COUNT string, BREEDING BIRD ATLAS CODE string, BREEDING BIRD ATLAS CATEGORY string, AGE/SEX string, COUNTRY string, COUNTRY CODE string, STATE string, STATE CODE string, COUNTY string, COUNTY CODE string, IBA CODE string, BCR CODE uint8, USFWS CODE string, ATLAS BLOCK string, LOCALITY string, LOCALITY ID string, LOCALITY TYPE string, LATITUDE y_coordinate, LONGITUDE x_coordinate, OBSERVATION DATE string, TIME OBSERVATIONS STARTED string, OBSERVER ID string,
      SAMPLING EVENT IDENTIFIER string, PROTOCOL TYPE string, PROTOCOL CODE string, PROJECT CODE string, DURATION MINUTES uint16, EFFORT DISTANCE KM real32, EFFORT AREA HA real64, NUMBER OBSERVERS uint8, ALL SPECIES REPORTED uint8, GROUP IDENTIFIER string, HAS MEDIA uint8, APPROVED uint8, REVIEWED uint8, REASON string, TRIP COMMENTS string, SPECIES COMMENTS string, col46 string
    -> FormatTester_name

Bookmark: Output eBird values in MARC accepts List
ebird_filtered (writer CSV2_2)
    attributes: COMMON NAME string, OBSERVATION COUNT string, STATE string, COUNTY string, COUNTY CODE string, LOCALITY string, LATITUDE y_coordinate, LONGITUDE x_coordinate, OBSERVATION DATE string, TRIP COMMENTS string, SPECIES COMMENTS string, OBSERVER ID string, SCIENTIFIC NAME string
